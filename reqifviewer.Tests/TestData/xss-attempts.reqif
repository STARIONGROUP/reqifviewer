# XSS attempts <img src=x onerror="window.__xss=(window.__xss||0)+1">

# Specification: XSS attempts

## REQ-1: Legitimate formatting
The machine shall brew coffee.
| a | b |
| --- | --- |
a safe link

## REQ-2: Script element
Before after

## REQ-3: Event handler on an image
Image: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

## REQ-4: javascript: link
click me

## REQ-5: SVG onload
SVG

## REQ-6: Overlay with a fixed position
Overlay

## <script>window.__xss=(window.__xss||0)+1</script>: <img src=x onerror="window.__xss=(window.__xss||0)+1"> in the long name
The long name and the ID contain markup

## _so-unnamed
Unnamed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
